A DEFINITIONS

-- [(AUTOMATIC|EXPLICIT|IMPLICIT) TAGS]
-- the default is EXPLICIT TAGS
  AUTOMATIC TAGS ::=

BEGIN
-- EXPORTS <exports clause>;
IMPORTS;
-- MODULE-BODY
MyInteger ::= INTEGER 

MySeqInt ::= SEQUENCE { i INTEGER } 

MySeqOfInt ::= SEQUENCE OF INTEGER

MyValues ::= INTEGER ( 1 | 2 |3 )

END
